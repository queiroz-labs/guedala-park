"""Salvar o projeto completo com serializacao binaria e todas as funcoes.

Escolha o destino na janela. A preferencia global anterior e restaurada.
Use esta macro apos editar para manter a otimizacao do arquivo.
"""
from pathlib import Path
import runpy
import FreeCAD as App
import FreeCADGui as Gui
from PySide import QtWidgets

if App.ActiveDocument is None:
    raise RuntimeError('Abra o projeto antes de salvar.')
folder=Path(__file__).resolve().parent
default=Path(App.ActiveDocument.FileName) if App.ActiveDocument.FileName else folder/'Guedala_Park_Completo_Otimizado.FCStd'
chosen,_=QtWidgets.QFileDialog.getSaveFileName(Gui.getMainWindow(),'Salvar projeto completo otimizado',str(default),'FreeCAD (*.FCStd)')
if chosen:
    library=runpy.run_path(str(folder/'serializacao_binaria.py'))
    report=library['salvar_documento'](App.ActiveDocument,chosen)
    App.Console.PrintMessage('Projeto completo salvo: '+str(report)+'\n')
