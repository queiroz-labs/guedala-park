import FreeCAD as A, FreeCADGui as G, Part, pathlib, json, hashlib, traceback
from PySide import QtCore, QtGui
p=pathlib.Path(r'C:\Users\Elias\Documents\PROJETOS\Guedala park\guedala-park\01_Projeto\Modelo_FreeCAD\01_Atual\FGVTN_R44_2026-10-22')
def sha(f):return hashlib.sha256(f.read_bytes()).hexdigest()
def snap(d):
 r={}
 for o in d.Objects:
  r[o.Name]={'label':o.Label,'placement':str(o.Placement) if hasattr(o,'Placement') else None,'color':list(o.ViewObject.ShapeColor) if hasattr(o.ViewObject,'ShapeColor') else None,'visibility':o.ViewObject.Visibility}
 return r
try:
 source=p.parent/'Consolidacao_R43_2026-10-21/Guedala_Park_R43_Consolidado.FCStd'
 (p/'Fase_R44.txt').write_text('abrindo R43',encoding='utf8')
 oldhash=sha(source);d=A.openDocument(str(source),hidden=True);before=snap(d)
 (p/'Fase_R44.txt').write_text('R43 aberta; snapshot leve concluido; importando referencias',encoding='utf8')
 root=d.addObject('App::DocumentObjectGroup','FGVTN_R44_Referencia');root.Label='FGVTN R44 — STEP 400 fabricante; montagem NÃO validada'
 root.addProperty('App::PropertyString','Status');root.Status='Uma lateral, seis sólidos. Engates não identificados. Datum de montagem não estabelecido. R04 continua estudo; não fabricar.'
 root.addProperty('App::PropertyString','GeometriaRecebida');root.GeometriaRecebida='BASE_400mm mede 297 mm; curso móvel 374,3 mm. Não extrapolar para 500 mm.'
 for st in ['FECHADA','ABERTA']:
  sd=A.openDocument(str(p/(st+'_400_GUI_INSPECAO.FCStd')))
  g=d.addObject('App::DocumentObjectGroup','FGVTN_R44_'+st);g.Label=st+' — coordenadas originais do STEP, não instalada';root.addObject(g)
  for old in sd.Objects:
   if old.TypeId!='Part::Feature':continue
   n=d.addObject('PartDesign::Feature','FGVTN_R44_'+st+'_'+old.Name);n.Label=old.Label
   q=old.Shape.copy();q.Placement=old.getGlobalPlacement();n.Shape=q;g.addObject(n);n.ViewObject.ShapeColor=(0.72,0.74,0.77)
   n.addProperty('App::PropertyString','Fonte');n.Fonte='54FGOC12400TSX0_'+st+'.STEP; exportado 2022-10-06; recebido 2026-10-22'
  g.Visibility=False
  A.closeDocument(sd.Name)
 root.Visibility=False
 d.Label='Guedala Park R44 — fontes FGVTN 400; montagem pendente'
 (p/'Fase_R44.txt').write_text('salvando R44',encoding='utf8')
 out=p/'Guedala_Park_R44_Consolidado.FCStd';d.saveAs(str(out));A.closeDocument(d.Name)
 (p/'Fase_R44.txt').write_text('reabrindo R44',encoding='utf8')
 d=A.openDocument(str(out),hidden=True);after=snap(d)
 diffs=[n for n,v in before.items() if n not in after or v!=after[n]]
 report={'source':str(source),'source_sha256_before':oldhash,'source_sha256_after':sha(source),'output':str(out),'output_sha256':sha(out),'original_solid_objects':len(before),'original_changes':diffs,'new_manufacturer_solid_objects':len([n for n in after if n.startswith('FGVTN_R44_')]),'removed_supports_absent':all(d.getObject(n) is None for n in ['Peca108','Peca109']),'r04_not_incorporated':True,'references_hidden':not d.getObject('FGVTN_R44_Referencia').Visibility,'original_snapshot':before}
 (p/'Verificacao_R44.json').write_text(json.dumps(report,indent=2,ensure_ascii=False),encoding='utf8')
 assert not diffs and oldhash==sha(source)
 # Comparação lado a lado: mesma vista e escala, fontes não alteradas.
 comp=A.newDocument('Comparacao_STEP400')
 for i,st in enumerate(['FECHADA','ABERTA']):
  for old in d.getObject('FGVTN_R44_'+st).Group:
   n=comp.addObject('PartDesign::Feature',st+'_'+old.Name);q=old.Shape.copy();q.translate(A.Vector(i*160,0,0));n.Shape=q;n.ViewObject.ShapeColor=(0.75,0.76,0.79) if i==0 else (0.3,0.65,0.85)
 comp.recompute();G.getDocument(comp.Name).activeView().viewFront();G.getDocument(comp.Name).activeView().fitAll();G.updateGui()
 G.getDocument(comp.Name).activeView().saveImage(str(p/'STEP400_mesma_escala.png'),1200,1000,'White');comp.saveAs(str(p/'Comparacao_STEP400_ESTUDO.FCStd'))
 (p/'Consolidacao_OK.txt').write_text('R44 salva e reaberta; '+str(len(before))+' geometrias originais preservadas.',encoding='utf8')
except Exception:
 (p/'Consolidacao_ERRO.txt').write_text(traceback.format_exc(),encoding='utf8')
QtCore.QTimer.singleShot(200,QtGui.QApplication.quit)
