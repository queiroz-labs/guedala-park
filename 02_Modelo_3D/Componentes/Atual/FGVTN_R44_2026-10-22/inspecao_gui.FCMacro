import FreeCAD as A,FreeCADGui as G,ImportGui,pathlib,json,traceback
from PySide import QtCore,QtGui
p=pathlib.Path(r'C:\Users\Elias\Documents\PROJETOS\Guedala park\guedala-park\01_Projeto\Modelo_FreeCAD\01_Atual\FGVTN_R44_2026-10-22')
try:
 for label in ['FECHADA','ABERTA']:
  d=A.newDocument('FGVTN400_'+label);ImportGui.insert(str(p/'Fontes'/('54FGOC12400TSX0_'+label+'.STEP')),d.Name)
  d.recompute();A.setActiveDocument(d.Name);G.activeDocument().activeView().viewAxonometric();G.activeDocument().activeView().fitAll();G.updateGui()
  G.activeDocument().activeView().saveImage(str(p/('STEP400_'+label+'_axono.png')),1200,800,'White')
  G.activeDocument().activeView().viewFront();G.activeDocument().activeView().fitAll();G.updateGui()
  G.activeDocument().activeView().saveImage(str(p/('STEP400_'+label+'_frente.png')),1200,800,'White')
  d.saveAs(str(p/(label+'_400_GUI_INSPECAO.FCStd')))
 (p/'Inspecao_GUI_OK.txt').write_text('Importacao nativa ImportGui, imagens e FCStd salvos.',encoding='utf-8')
except:
 (p/'Inspecao_GUI_ERRO.txt').write_text(traceback.format_exc(),encoding='utf-8')
QtCore.QTimer.singleShot(200,QtGui.QApplication.quit)
