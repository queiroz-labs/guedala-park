from pathlib import Path
import json, traceback, hashlib
import FreeCAD as App, FreeCADGui as Gui, Part

root = Path(r'C:\Users\Elias\Documents\PROJETOS\Guedala park\guedala-park')
dest = root / '02_Modelo_3D/Historico/Fichas_no_CAD'
source = root / '03_Ambientes/Cozinha/Rodizios_gaveta/Guedala_Park_R45_Rodizios_P08.FCStd'
target = dest / 'Guedala_Park_R46_Fichas_R14.FCStd'
data = json.loads((dest / 'Entrada_R46.json').read_text(encoding='utf-8'))
FGVTN500 = 'FGVTN 54FGOC12500TSX0'


def snapshot(doc):
    # Assinatura geométrica: o recálculo troca o hashCode da forma e deixa ruído de 1e-17 nas
    # posições guiadas por expressão (portas), sem mudar a geometria. Arredondar a 1e-9 mm.
    def r(values):
        return [round(v, 9) + 0.0 for v in values]
    result = {}
    for o in doc.Objects:
        record = {'placement': r(o.Placement.toMatrix().A)} if hasattr(o, 'Placement') else {}
        if o.isDerivedFrom('Part::Feature') and not o.Shape.isNull():
            s, b = o.Shape, o.Shape.BoundBox
            record.update(volume=round(s.Volume, 6), area=round(s.Area, 6), faces=len(s.Faces), vertices=len(s.Vertexes),
                          bbox=r([b.XMin, b.YMin, b.ZMin, b.XMax, b.YMax, b.ZMax]),
                          center=r(sum((x.CenterOfMass * x.Volume for x in s.Solids), App.Vector()) / sum(x.Volume for x in s.Solids)) if s.Solids and sum(x.Volume for x in s.Solids) > 0 else None)
        result[o.Name] = record
    return result


def prop(obj, kind, name, value, group='Ficha R14'):
    if name not in obj.PropertiesList:
        obj.addProperty(kind, name, group)
    setattr(obj, name, value)


def global_shape(o):
    sh = o.Shape.copy()
    sh.Placement = o.getGlobalPlacement()
    return sh


try:
    Gui.getMainWindow().hide()
    assert not target.exists(), 'A R46 já existe; não sobrescrever sem conferência.'
    source_hash = hashlib.sha256(source.read_bytes()).hexdigest()
    doc = App.openDocument(str(source))
    before = snapshot(doc)
    doc.openTransaction('R46: fichas R14 no CAD')

    # 1. Cada módulo e cada peça recebem os dados vigentes das fichas.
    sheet = doc.addObject('Spreadsheet::Sheet', 'FichasR14')
    sheet.Label = 'R46 · fichas R14 por módulo (dados do projeto, não liberação)'
    doc.getObject('Documentacao').addObject(sheet)
    for col, title in zip('ABCDE', ['Código', 'Objeto CAD', 'Módulo', 'Resumo R14', 'Ficha']):
        sheet.set(f'{col}1', title)
    panels_done = 0
    for row, (code, m) in enumerate(sorted(data['modules'].items()), 2):
        mod = doc.getObject(m['cadModule'])
        assert mod is not None and mod.TypeId == 'App::Part', (code, m['cadModule'])
        prop(mod, 'App::PropertyString', 'CodigoFichaR14', code)
        prop(mod, 'App::PropertyString', 'ResumoR14', m['summary'])
        prop(mod, 'App::PropertyStringList', 'FerragensR14', m['hardware'])
        prop(mod, 'App::PropertyString', 'FichaR14', m['sheet'])
        prop(mod, 'App::PropertyString', 'StatusR14', 'Dados das fichas R14 gravados em 24/10/2026. Seleções de projeto; medidas reais, protótipos e liberação de fabricação pendentes.')
        for col, value in zip('ABCDE', [code, m['cadModule'], m['name'], m['summary'], m['sheet']]):
            sheet.set(f'{col}{row}', "'" + value)
        for pid, p in m['panels'].items():
            part = doc.getObject(pid)
            assert part is not None, pid
            prop(part, 'App::PropertyString', 'EspecificacaoR14', p['spec'])
            prop(part, 'App::PropertyString', 'ModuloR14', code)
            panels_done += 1

    # 2. Gavetas P01/P06: a geometria Blum fica como envelope; a seleção é FGVTN 500 (sem STEP 500 oficial).
    guides = [o for o in doc.Objects if o.Label.startswith('MOVENTO500 ·')]
    for o in guides:
        o.Label = 'Envelope MOVENTO500 (STEP Blum) · seleção R14 ' + FGVTN500 + ' · ' + o.Label.split(' · ', 1)[1]
        prop(o, 'App::PropertyString', 'StatusR14', f'Seleção R14: {FGVTN500}. A geometria é o STEP Blum MOVENTO 500 usado como envelope; não há STEP oficial FGVTN 500 e o de 400 não deve ser extrapolado. Engates e fixadores pelo kit recebido.')
    g2 = doc.getObject('GuiasG2R07')
    g2.Label = 'Guias G2 — montagem STEP R07 como envelope · seleção R14 ' + FGVTN500
    prop(g2, 'App::PropertyString', 'StatusR14', f'Seleção R14: {FGVTN500}, como em G1/G3. A montagem STEP da proposta R07 fica como envelope; engates e fixadores pelo kit recebido.')
    guides.append(g2)
    movento400 = [o for o in doc.Objects if o.Label.startswith('MOVENTO400 ·') and o.TypeId == 'Part::Feature']
    for o in movento400:
        prop(o, 'App::PropertyString', 'StatusR14', 'Seleção R14 confirmada: Blum MOVENTO 760H4000S com BLUMOTION S e engates T51.7601. Corrigir interferências antes de usinar.')

    # 3. Grupos de candidatas superadas passam a dizer o que valeu.
    fg = doc.getObject('FGVTN_R42')
    fg.Label = 'FGVTN R42 — histórico: dobradiças superadas por Blum 71B3550; FGVTN 500 vale só em P01/P06 (R14)'
    doc.getObject('FGVTN_R42_Dobradicas').Label = 'FGVTN candidata - 46 dobradicas comuns — SUPERADA (R14: Blum CLIP top BLUMOTION 71B3550, 52 posições)'
    for o in fg.Group:
        if o.Name.startswith('FGVTN_R42_Gaveta'):
            o.Label = o.Label + (' — R14: MOVENTO 400' if o.Name in ('FGVTN_R42_Gaveta008', 'FGVTN_R42_Gaveta009') else ' — R14: ' + FGVTN500 + ' onde a ficha indicar')

    # 4. Banco P20: mecanismo vigente registrado; estudos Southco/Rockler ficam como histórico.
    banco = doc.getObject('Modulo019')
    prop(banco, 'App::PropertyString', 'MecanismoTampasR14', 'Dobradiça piano na borda traseira de cada tampa + par de articuladores com trava por tampa (diretriz 23/10). Southco E6 R47 é alternativa histórica. Eixo, apoio da piano e terminais dependem do protótipo; não há ferragem modelada.')
    doc.getObject('BancoDuasTampasR43').Label = 'Banco R43 — duas tampas e duas almofadas · mecanismo R14: piano + trava (não modelado)'

    # 5. Minifix das fichas: marcadores Ø15 dentro das peças, sem furar a chapa.
    group = doc.addObject('App::DocumentObjectGroup', 'MinifixR14')
    group.Label = 'R46 · 52 Minifix das fichas R14 — marcadores Ø15, peças NÃO furadas'
    sub = {}
    frame18 = doc.getObject('Modulo018').getGlobalPlacement()
    markers = []
    for i, p in enumerate(data['minifix'], 1):
        code = p['module']
        if code not in sub:
            g = doc.addObject('App::DocumentObjectGroup', f'MinifixR14_{code}')
            g.Label = f'{code} · {sum(1 for x in data["minifix"] if x["module"] == code)} caixas Minifix 15 (Häfele 262.26.034 + pino S100)'
            group.addObject(g); sub[code] = g
        point, axis = App.Vector(*p['point']), App.Vector(*p['axis'])
        if p['frame'] == 'Modulo018':
            point, axis = frame18.multVec(point), frame18.Rotation.multVec(axis)
        marker = doc.addObject('Part::Feature', f'MinifixR14_{code}_')
        marker.Shape = Part.makeCylinder(7.5, p['depth'], point, axis)
        marker.Label = f'{code} · Minifix {p["board"]} · Ø15×{p["depth"]:g} — marcador nominal'
        prop(marker, 'App::PropertyString', 'StatusR14', 'Posição nominal das fichas R14. Não é furação CNC: provar em retalho e na chapa real.')
        prop(marker, 'App::PropertyString', 'PecaR14', p['board'])
        marker.ViewObject.ShapeColor = (0.95, 0.55, 0.10)
        sub[code].addObject(marker)
        board = doc.getObject(p['board'])
        inside = global_shape(board).common(marker.Shape).Volume / marker.Shape.Volume
        assert inside > 0.999, (marker.Name, p['board'], inside)
        markers.append(dict(module=code, marker=marker.Name, board=p['board'], center_global_mm=[round(c, 3) for c in point], axis=[round(c, 6) for c in axis], depth_mm=p['depth'], inside_board=round(inside, 6)))

    doc.commitTransaction(); doc.recompute()
    added = {sheet.Name, group.Name} | {g.Name for g in sub.values()} | {m['marker'] for m in markers}
    after = {k: v for k, v in snapshot(doc).items() if k not in added}
    differences = {k: dict(before=before.get(k), after=after.get(k)) for k in set(before) | set(after) if before.get(k) != after.get(k)}
    (dest / 'Diferencas_CAD.json').write_text(json.dumps(differences, ensure_ascii=False, indent=2), encoding='utf-8')
    assert not differences, 'Geometria/posição existente mudou; conferir Diferencas_CAD.json.'
    doc.Label = 'Guedala Park · R46 · geometria R45, cores R16, P08 e fichas R14'
    doc.saveAs(str(target))
    objects = len(doc.Objects)
    App.closeDocument(doc.Name)

    # Reabrir e conferir o que foi salvo.
    check = App.openDocument(str(target))
    assert len(check.Objects) == objects
    assert sum(1 for o in check.Objects if o.Name.startswith('MinifixR14_') and o.TypeId == 'Part::Feature') == 52
    assert all(check.getObject(m['cadModule']).CodigoFichaR14 == c for c, m in data['modules'].items())
    assert sum(1 for o in check.Objects if 'EspecificacaoR14' in o.PropertiesList) == panels_done
    reopened = {k: v for k, v in snapshot(check).items() if k not in added}
    assert reopened == after, 'Geometria diferente após reabrir.'
    colored = check.getObject(markers[0]['marker']).ViewObject.ShapeColor[:3]
    App.closeDocument(check.Name)
    assert hashlib.sha256(source.read_bytes()).hexdigest() == source_hash

    report = dict(date='2026-10-24', source=str(source), sourceSHA256=source_hash, file=str(target),
                  SHA256=hashlib.sha256(target.read_bytes()).hexdigest(), objects=objects, added_objects=len(added),
                  unmodified_objects=len(before), other_geometry_and_placements_preserved=True, reopened=True,
                  modules=len(data['modules']), panels_with_spec=panels_done, minifix_markers=len(markers),
                  minifix_by_module={c: sum(1 for m in markers if m['module'] == c) for c in sub},
                  fgvtn500_envelopes_relabeled=len(guides), fgvtn500_drawers='P01: 4 gavetas (16 peças MOVENTO500); P06: G1 e G3 (8 peças MOVENTO500) + G2 (montagem GuiasG2R07)', movento400_confirmed=len(movento400),
                  marker_color_after_reopen=[round(c, 3) for c in colored], markers=markers,
                  scope='Fichas R14 gravadas como propriedades e marcadores. Nenhuma peça furada, movida ou redimensionada; R45/P08 preservado. FGVTN 500 sem STEP oficial: envelope Blum mantido. Piano do banco não modelado (depende do protótipo).')
    (dest / 'Verificacao_R46.json').write_text(json.dumps(report, ensure_ascii=False, indent=2), encoding='utf-8')
except Exception:
    (dest / 'Erro_CAD.txt').write_text(traceback.format_exc(), encoding='utf-8')
finally:
    from PySide import QtCore
    for d in list(App.listDocuments().values()):
        App.closeDocument(d.Name)
    QtCore.QTimer.singleShot(0, Gui.getMainWindow().close)
