from pathlib import Path
import json, traceback, hashlib
import FreeCAD as App, FreeCADGui as Gui

root = Path(r'C:\Users\Elias\Documents\PROJETOS\Guedala park\guedala-park')
dest = root / '02_Modelo_3D/Historico/Depurador_sem_canal'
source = root / '02_Modelo_3D/Historico/Fichas_no_CAD/Guedala_Park_R46_Fichas_R14.FCStd'
target = dest / 'Guedala_Park_R48_Depurador_sem_canal.FCStd'
REMOVED = 'Peca321'
DIVIDER = 'Peca320'
RESUMO = 'Blum nas duas portas. Depurador sem duto: canal central removido e divisor levado até o fundo na R48 (dois nichos 298 × 312).'


def snapshot(doc):
    # Mesma assinatura geométrica da R46 (arredondada a 1e-9 mm).
    def r(values):
        return [round(v, 9) + 0.0 for v in values]
    result = {}
    for o in doc.Objects:
        record = {'placement': r(o.Placement.toMatrix().A)} if hasattr(o, 'Placement') else {}
        if o.isDerivedFrom('Part::Feature') and not o.Shape.isNull():
            s, b = o.Shape, o.Shape.BoundBox
            record.update(volume=round(s.Volume, 6), area=round(s.Area, 6), faces=len(s.Faces), vertices=len(s.Vertexes),
                          bbox=r([b.XMin, b.YMin, b.ZMin, b.XMax, b.YMax, b.ZMax]),
                          center=r(sum((x.CenterOfMass * x.Volume for x in s.Solids), App.Vector()) / sum(x.Volume for x in s.Solids)) if s.Solids and sum(x.Volume for x in s.Solids) > 0 else None)
        result[o.Name] = record
    return result


def appearance(doc):
    return {o.Name: [str(getattr(o.ViewObject, p, None)) for p in ('ShapeColor', 'DiffuseColor', 'ShapeAppearance', 'Visibility', 'Transparency')]
            for o in doc.Objects if o.ViewObject is not None}


try:
    Gui.getMainWindow().hide()
    assert not target.exists(), 'A R48 já existe; não sobrescrever sem conferência.'
    source_hash = hashlib.sha256(source.read_bytes()).hexdigest()
    doc = App.openDocument(str(source))
    channel = doc.getObject(REMOVED)
    assert channel.Label.startswith('Reserva canal técnico'), channel.Label
    assert [o.Name for o in channel.InList] == ['Modulo008'] and not channel.OutList
    removed_bbox = [round(v, 3) for v in (channel.Shape.BoundBox.XMin, channel.Shape.BoundBox.YMin, channel.Shape.BoundBox.ZMin,
                                          channel.Shape.BoundBox.XMax, channel.Shape.BoundBox.YMax, channel.Shape.BoundBox.ZMax)]
    # Reservas ocultas sem decisão aprovada (revisão de 24/10): nenhuma tem dependentes.
    group = doc.getObject('ReservasTecnicasR31')
    hidden = ['Peca250', 'R45_Ref_Faixa_cadeira', group.Name] + [o.Name for o in group.Group]
    hidden_removed = []
    for n in hidden:
        o = doc.getObject(n)
        assert not [x for x in o.InList if x.Name not in hidden + ['Ambiente_quarto', 'Documentacao', 'R45_Ref_Bancada_Estrutura_R45_R02_ESTUDO']], (n, o.InList)
        assert not [x for x in o.OutList if x.Name not in hidden], (n, o.OutList)
        hidden_removed.append(dict(name=n, label=o.Label))
    body = doc.getObject('R45_Ref_Bancada_Estrutura_R45_R02_ESTUDO')
    assert body.TypeId == 'App::DocumentObjectGroup'  # grupo simples: a faixa não alimenta outra forma
    gone = set(hidden) | {REMOVED}
    before = {k: v for k, v in snapshot(doc).items() if k not in gone | {DIVIDER}}
    looks = {k: v for k, v in appearance(doc).items() if k not in gone}

    doc.openTransaction('R48: depurador sem canal de duto')
    mod = doc.getObject('Modulo008')
    mod.removeObject(channel)
    doc.removeObject(REMOVED)
    divider = doc.getObject(DIVIDER)
    assert divider.Width.Value == 118 and divider.LocalY.Value == 20
    divider.Width = 312  # de Y20 até a face do fundo em Y332
    mod.ResumoR14 = RESUMO
    mod.addProperty('App::PropertyString', 'StatusR48', 'Revisão R48')
    mod.StatusR48 = ('24/10/2026: Suggar DE61IX em modo depurador não tem duto. Removida a reserva central 196×178×556 (Peca321), '
                     'que era ilustrativa e nunca aprovada. Preservar a abertura de retorno de ar de 20 mm na largura do armário '
                     '(manual DE61IX REV.0025), filtros e acesso. Divisor 18 (Peca320) passa de 118 para 312 de profundidade, até o fundo: dois nichos 298 × 312 × 556. Prateleiras não modeladas.')
    sheet = doc.getObject('FichasR14')
    row = next(r for r in range(2, 30) if sheet.getContents(f'B{r}') in ("'Modulo008", 'Modulo008'))
    sheet.set(f'D{row}', "'" + RESUMO)
    doc.getObject('Ambiente_quarto').removeObject(doc.getObject('Peca250'))
    body.removeObject(doc.getObject('R45_Ref_Faixa_cadeira'))
    for n in [o.Name for o in group.Group]:
        group.removeObject(doc.getObject(n)); doc.removeObject(n)
    doc.getObject('Documentacao').removeObject(group)
    for n in ('Peca250', 'R45_Ref_Faixa_cadeira', 'ReservasTecnicasR31'):
        doc.removeObject(n)
    doc.commitTransaction(); doc.recompute()

    after = snapshot(doc)
    b = doc.getObject(DIVIDER).Shape.BoundBox
    divider_bbox = [round(v, 6) for v in (b.XMin, b.YMin, b.ZMin, b.XMax, b.YMax, b.ZMax)]
    assert divider_bbox == [-334, 20, 18, -316, 332, 574], divider_bbox
    fundo = doc.getObject('Peca317').Shape.BoundBox
    assert fundo.YMin == 332 and fundo.XMin < -334 and fundo.XMax > -316
    after_other = {k: v for k, v in after.items() if k != DIVIDER}
    differences = {k: dict(before=before.get(k), after=after.get(k)) for k in set(before) | set(after_other) if before.get(k) != after_other.get(k)}
    (dest / 'Diferencas_CAD.json').write_text(json.dumps(differences, ensure_ascii=False, indent=2), encoding='utf-8')
    assert not differences, 'Geometria/posição existente mudou; conferir Diferencas_CAD.json.'
    assert appearance(doc) == looks, 'Aparência mudou.'
    doc.Label = 'Guedala Park · R48 · R46 com depurador sem canal de duto'
    doc.saveAs(str(target))
    objects = len(doc.Objects)
    App.closeDocument(doc.Name)

    check = App.openDocument(str(target))
    assert len(check.Objects) == objects and all(check.getObject(n) is None for n in gone)
    assert snapshot(check) == after, 'Geometria diferente após reabrir.'
    assert appearance(check) == looks, 'Aparência diferente após reabrir.'
    assert check.getObject('Modulo008').ResumoR14 == RESUMO
    App.closeDocument(check.Name)
    assert hashlib.sha256(source.read_bytes()).hexdigest() == source_hash

    report = dict(date='2026-10-24', source=str(source), sourceSHA256=source_hash, file=str(target),
                  SHA256=hashlib.sha256(target.read_bytes()).hexdigest(), objects=objects,
                  changed=dict(name=DIVIDER, label='Divisória005', width_mm=[118, 312], bbox_mm=divider_bbox),
                  removed=dict(name=REMOVED, label='Reserva canal técnico · sem armazenamento', module='Modulo008', bbox_mm=removed_bbox),
                  hidden_reserves_removed=hidden_removed,
                  other_objects_preserved=len(before), appearance_properties_preserved=len(looks) * 5, reopened=True,
                  scope='Aéreo D: reserva do canal removida e divisor estendido até o fundo; textos do módulo e da tabela R14 atualizados. '
                        'Removidas reservas ocultas sem decisão: proteção lateral 10 mm do quarto, faixa de cadeira 800×500×720 e grupo R31 da cocção. '
                        'Nenhuma outra peça movida ou redimensionada.')
    (dest / 'Verificacao_R48.json').write_text(json.dumps(report, ensure_ascii=False, indent=2), encoding='utf-8')
except Exception:
    (dest / 'Erro_CAD.txt').write_text(traceback.format_exc(), encoding='utf-8')
finally:
    from PySide import QtCore
    for d in list(App.listDocuments().values()):
        App.closeDocument(d.Name)
    QtCore.QTimer.singleShot(0, Gui.getMainWindow().close)
